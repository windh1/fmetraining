FME workspace Basics-Ex1-Complete.fmw

Parameters:
- SourceDataset_GML = C:\FMEData2018\Data\Emergency\FireHalls.gml   # Source Geography Markup Language (GML) File(s)
- SourceDataset_OGCKML = C:\FMEData2018\Data\Boundaries\VancouverNeighborhoods.kml   # Source Google KML File or URL

Readers:
- GML_1: GML from $(SourceDataset_GML)
- OGCKML_1: OGCKML from $(SourceDataset_OGCKML)

Writers:
- NULL_1: NULL

FireHalls (reader GML_1)
    attributes: HallNumber xml_char(30), Name xml_char(30), Address xml_char(30), PhoneNumber xml_char(30), Engine xml_char(1), Ladder xml_char(1), Quint xml_char(1), Rescue xml_char(1), Medic xml_char(1), gml_pointProperty xml_geometry, gml_multiPointProperty xml_geometry
    -> Clipper [CLIPPEE]
Neighborhoods (reader OGCKML_1)
    attributes: NeighborhoodId kml_buffer, NeighborhoodName kml_buffer, NeighborhoodURL kml_buffer, TotalPopulation2001 kml_buffer, TotalPopulation2011 kml_buffer
    -> Reprojector
Reprojector
    DEST = UTM83-10
    INTERPOLATION_TYPE_NAME = Nearest Neighbor
    RASTER_CELL_SIZE = Preserve Cells
    RASTER_TOLERANCE = 0.0
    SOURCE = Read from feature
    REPROJECTED -> Clipper [CLIPPER]
    REPROJECTED -> Neighborhoods (writer NULL_1)
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> FireHalls (writer NULL_1)
FireHalls (writer NULL_1)
    attributes: gml_parent_id char(255), gml_parent_property char(255), gml_id char(255), HallNumber char(30), Name char(30), Address char(30), PhoneNumber char(30), Engine char(1), Ladder char(1), Quint char(1), Rescue char(1), Medic char(1), gml_pointProperty char(255), gml_multiPointProperty char(255)
Neighborhoods (writer NULL_1)
    attributes: NeighborhoodId char(255), NeighborhoodName char(255), NeighborhoodURL char(255), TotalPopulation2001 char(255), TotalPopulation2011 char(255)
